-- RFC 5652: 12.1.  CMS ASN.1 Module

--## CryptographicMessageSyntax2004
--##   { iso(1) member-body(2) us(840) rsadsi(113549) 
--##     pkcs(1) pkcs-9(9) smime(16) modules(0) cms-2004(24) }

--## DEFINITIONS IMPLICIT TAGS ::=
--## BEGIN

-- EXPORTS All
-- The types and values defined in this module are exported for use
-- in the other ASN.1 modules.  Other applications may use them for
-- their own purposes.

--## IMPORTS
--## 
--##   -- Imports from RFC 5280 [PROFILE], Appendix A.1
--##         AlgorithmIdentifier, Certificate, CertificateList,
--##         CertificateSerialNumber, Name
--##            FROM PKIX1Explicit88
--##                 { iso(1) identified-organization(3) dod(6)
--##                   internet(1) security(5) mechanisms(5) pkix(7)
--##                   mod(0) pkix1-explicit(18) }
--## 
--##   -- Imports from RFC 3281 [ACPROFILE], Appendix B
--##         AttributeCertificate
--##            FROM PKIXAttributeCertificate
--##                 { iso(1) identified-organization(3) dod(6)
--##                   internet(1) security(5) mechanisms(5) pkix(7)
--##                   mod(0) attribute-cert(12) }
--## 
--##   -- Imports from Appendix B of this document
--##         AttributeCertificateV1
--##            FROM AttributeCertificateVersion1
--##                 { iso(1) member-body(2) us(840) rsadsi(113549)
--##                   pkcs(1) pkcs-9(9) smime(16) modules(0)
--##                   v1AttrCert(15) } ;

 AlgorithmIdentifier  ::=  SEQUENCE  {
      algorithm               OBJECT IDENTIFIER,
      parameters              ANY DEFINED BY algorithm OPTIONAL  }

Certificate  ::=  SEQUENCE  {
     tbsCertificate       PKIX1Explicit88__TBSCertificate,
     signatureAlgorithm   AlgorithmIdentifier,
     signature            BIT STRING  }

PKIX1Explicit88__TBSCertificate  ::=  SEQUENCE  {
     version         [0]  EXPLICIT PKIX1Explicit88__Version,
     serialNumber         CertificateSerialNumber,
     signature            AlgorithmIdentifier,
     issuer               Name,
     validity             PKIX1Explicit88__Validity,
     subject              Name,
     subjectPublicKeyInfo PKIX1Explicit88__SubjectPublicKeyInfo,
     issuerUniqueID  [1]  IMPLICIT PKIX1Explicit88__UniqueIdentifier OPTIONAL,
                          -- If present, version MUST be v2 or v3
     subjectUniqueID [2]  IMPLICIT PKIX1Explicit88__UniqueIdentifier OPTIONAL,
                          -- If present, version MUST be v2 or v3
     extensions      [3]  EXPLICIT PKIX1Explicit88__Extensions OPTIONAL
                          -- If present, version MUST be v3 --
}

PKIX1Explicit88__Version  ::=  INTEGER

PKIX1Explicit88__Validity ::= SEQUENCE {
     notBefore      Time,
     notAfter       Time  }

PKIX1Explicit88__UniqueIdentifier  ::=  BIT STRING

PKIX1Explicit88__SubjectPublicKeyInfo  ::=  SEQUENCE  {
     algorithm            AlgorithmIdentifier,
     subjectPublicKey     BIT STRING  }

PKIX1Explicit88__Extensions  ::=  SEQUENCE OF PKIX1Explicit88__Extension
PKIX1Explicit88__Extension  ::=  SEQUENCE  {
     extnID      OBJECT IDENTIFIER,
     critical    BOOLEAN OPTIONAL,
     extnValue   OCTET STRING
}

CertificateList ::= ANY
CertificateSerialNumber  ::=  INTEGER

  Name ::= CHOICE { -- only one possibility for now --
     rdnSequence  PKIX1Explicit88__RDNSequence }

   PKIX1Explicit88__RDNSequence ::= SEQUENCE OF PKIX1Explicit88__RelativeDistinguishedName

   PKIX1Explicit88__RelativeDistinguishedName ::=
     SET OF PKIX1Explicit88__AttributeTypeAndValue
--##     SET SIZE (1..MAX) OF AttributeTypeAndValue

   PKIX1Explicit88__AttributeTypeAndValue ::= SEQUENCE {
     type     PKIX1Explicit88__AttributeType,
     value    PKIX1Explicit88__AttributeValue }

   PKIX1Explicit88__AttributeType ::= OBJECT IDENTIFIER

   PKIX1Explicit88__TeletexString ::= ANY
   PKIX1Explicit88__PrintableString ::= ANY

--##   AttributeValue ::= ANY -- DEFINED BY AttributeType
   PKIX1Explicit88__AttributeValue ::= CHOICE {
         teletexString     TeletexString  ,
         printableString   PrintableString,
         universalString   UniversalString,
         utf8String        UTF8String     ,
         bmpString         BMPString,
         ia5String         IA5String
   }


AttributeCertificate ::= OCTET STRING
AttributeCertificateV1 ::= OCTET STRING

-- Cryptographic Message Syntax

ContentInfo ::= SEQUENCE {
  contentType ContentType,
  content [0] EXPLICIT ANY DEFINED BY contentType }

ContentType ::= OBJECT IDENTIFIER

SignedData ::= SEQUENCE {
  version CMSVersion,
  digestAlgorithms DigestAlgorithmIdentifiers,
  encapContentInfo EncapsulatedContentInfo,
  certificates [0] IMPLICIT CertificateSet OPTIONAL,
  crls [1] IMPLICIT RevocationInfoChoices OPTIONAL,
  signerInfos SignerInfos }

DigestAlgorithmIdentifiers ::= SET OF DigestAlgorithmIdentifier

SignerInfos ::= SET OF SignerInfo

EncapsulatedContentInfo ::= SEQUENCE {
  eContentType ContentType,
  eContent [0] EXPLICIT OCTET STRING OPTIONAL }

SignerInfo ::= SEQUENCE {
  version CMSVersion,
  sid SignerIdentifier,
  digestAlgorithm DigestAlgorithmIdentifier,
  signedAttrs [0] IMPLICIT SignedAttributes OPTIONAL,
  signatureAlgorithm SignatureAlgorithmIdentifier,
  signature SignatureValue,
  unsignedAttrs [1] IMPLICIT UnsignedAttributes OPTIONAL }

SignerIdentifier ::= CHOICE {
  issuerAndSerialNumber IssuerAndSerialNumber,
  subjectKeyIdentifier [0] SubjectKeyIdentifier }

SignedAttributes ::= SET OF Attribute
--## SignedAttributes ::= SET SIZE (1..MAX) OF Attribute

UnsignedAttributes ::= SET OF Attribute
--## UnsignedAttributes ::= SET SIZE (1..MAX) OF Attribute

Attribute ::= SEQUENCE {
  attrType OBJECT IDENTIFIER,
  attrValues SET OF AttributeValue }

AttributeValue ::= ANY

SignatureValue ::= OCTET STRING

EnvelopedData ::= SEQUENCE {
  version CMSVersion,
  originatorInfo [0] IMPLICIT OriginatorInfo OPTIONAL,
  recipientInfos RecipientInfos,
  encryptedContentInfo EncryptedContentInfo,
  unprotectedAttrs [1] IMPLICIT UnprotectedAttributes OPTIONAL }   OriginatorInfo ::= SEQUENCE {
  certs [0] IMPLICIT CertificateSet OPTIONAL,
  crls [1] IMPLICIT RevocationInfoChoices OPTIONAL }

RecipientInfos ::= SET OF RecipientInfo
--## RecipientInfos ::= SET SIZE (1..MAX) OF RecipientInfo

EncryptedContentInfo ::= SEQUENCE {
  contentType ContentType,
  contentEncryptionAlgorithm ContentEncryptionAlgorithmIdentifier,
  encryptedContent [0] IMPLICIT EncryptedContent OPTIONAL }

-- EncryptedContent ::= ANY
-- EncryptedContent ::= SET OF OCTET STRING
EncryptedContent ::= OCTET STRING

UnprotectedAttributes ::= SET OF Attribute
--## UnprotectedAttributes ::= SET SIZE (1..MAX) OF Attribute

RecipientInfo ::= CHOICE {
  ktri KeyTransRecipientInfo,
  kari [1] KeyAgreeRecipientInfo,
  kekri [2] KEKRecipientInfo,
  pwri [3] PasswordRecipientInfo,
  ori [4] OtherRecipientInfo }

EncryptedKey ::= OCTET STRING

KeyTransRecipientInfo ::= SEQUENCE {
  version CMSVersion,  -- always set to 0 or 2
  rid RecipientIdentifier,
  keyEncryptionAlgorithm KeyEncryptionAlgorithmIdentifier,
  encryptedKey EncryptedKey }

RecipientIdentifier ::= CHOICE {
  issuerAndSerialNumber IssuerAndSerialNumber,
  subjectKeyIdentifier [0] SubjectKeyIdentifier }

KeyAgreeRecipientInfo ::= SEQUENCE {
  version CMSVersion,  -- always set to 3
  originator [0] EXPLICIT OriginatorIdentifierOrKey,
  ukm [1] EXPLICIT UserKeyingMaterial OPTIONAL,
  keyEncryptionAlgorithm KeyEncryptionAlgorithmIdentifier,
  recipientEncryptedKeys RecipientEncryptedKeys }

OriginatorIdentifierOrKey ::= CHOICE {
  issuerAndSerialNumber IssuerAndSerialNumber,
  subjectKeyIdentifier [0] SubjectKeyIdentifier,
  originatorKey [1] OriginatorPublicKey }

OriginatorPublicKey ::= SEQUENCE {
  algorithm AlgorithmIdentifier,
  publicKey BIT STRING }

RecipientEncryptedKeys ::= SEQUENCE OF RecipientEncryptedKey

RecipientEncryptedKey ::= SEQUENCE {
  rid KeyAgreeRecipientIdentifier,
  encryptedKey EncryptedKey }

KeyAgreeRecipientIdentifier ::= CHOICE {
  issuerAndSerialNumber IssuerAndSerialNumber,
  rKeyId [0] IMPLICIT RecipientKeyIdentifier }

RecipientKeyIdentifier ::= SEQUENCE {
  subjectKeyIdentifier SubjectKeyIdentifier,
  date GeneralizedTime OPTIONAL,
  other OtherKeyAttribute OPTIONAL }

SubjectKeyIdentifier ::= OCTET STRING

KEKRecipientInfo ::= SEQUENCE {
  version CMSVersion,  -- always set to 4
  kekid KEKIdentifier,
  keyEncryptionAlgorithm KeyEncryptionAlgorithmIdentifier,
  encryptedKey EncryptedKey }

KEKIdentifier ::= SEQUENCE {
  keyIdentifier OCTET STRING,
  date GeneralizedTime OPTIONAL,
  other OtherKeyAttribute OPTIONAL }

PasswordRecipientInfo ::= SEQUENCE {
  version CMSVersion,   -- always set to 0
  keyDerivationAlgorithm [0] KeyDerivationAlgorithmIdentifier
                             OPTIONAL,
  keyEncryptionAlgorithm KeyEncryptionAlgorithmIdentifier,
  encryptedKey EncryptedKey }

OtherRecipientInfo ::= SEQUENCE {
  oriType OBJECT IDENTIFIER,
  oriValue ANY DEFINED BY oriType }

DigestedData ::= SEQUENCE {
  version CMSVersion,
  digestAlgorithm DigestAlgorithmIdentifier,
  encapContentInfo EncapsulatedContentInfo,
  digest Digest }

Digest ::= OCTET STRING

EncryptedData ::= SEQUENCE {
  version CMSVersion,
  encryptedContentInfo EncryptedContentInfo,
  unprotectedAttrs [1] IMPLICIT UnprotectedAttributes OPTIONAL }

AuthenticatedData ::= SEQUENCE {
  version CMSVersion,
  originatorInfo [0] IMPLICIT OriginatorInfo OPTIONAL,
  recipientInfos RecipientInfos,
  macAlgorithm MessageAuthenticationCodeAlgorithm,
  digestAlgorithm [1] DigestAlgorithmIdentifier OPTIONAL,
  encapContentInfo EncapsulatedContentInfo,
  authAttrs [2] IMPLICIT AuthAttributes OPTIONAL,
  mac MessageAuthenticationCode,
  unauthAttrs [3] IMPLICIT UnauthAttributes OPTIONAL }

AuthAttributes ::= SET OF Attribute
--## AuthAttributes ::= SET SIZE (1..MAX) OF Attribute

UnauthAttributes ::= SET OF Attribute
--## UnauthAttributes ::= SET SIZE (1..MAX) OF Attribute

MessageAuthenticationCode ::= OCTET STRING

DigestAlgorithmIdentifier ::= AlgorithmIdentifier

SignatureAlgorithmIdentifier ::= AlgorithmIdentifier

KeyEncryptionAlgorithmIdentifier ::= AlgorithmIdentifier

ContentEncryptionAlgorithmIdentifier ::= AlgorithmIdentifier

MessageAuthenticationCodeAlgorithm ::= AlgorithmIdentifier

KeyDerivationAlgorithmIdentifier ::= AlgorithmIdentifier

RevocationInfoChoices ::= SET OF RevocationInfoChoice

RevocationInfoChoice ::= CHOICE {
  crl CertificateList,
  other [1] IMPLICIT OtherRevocationInfoFormat }

OtherRevocationInfoFormat ::= SEQUENCE {
  otherRevInfoFormat OBJECT IDENTIFIER,
  otherRevInfo ANY DEFINED BY otherRevInfoFormat }

CertificateChoices ::= CHOICE {
  certificate Certificate,
  extendedCertificate [0] IMPLICIT ExtendedCertificate,  -- Obsolete
  v1AttrCert [1] IMPLICIT AttributeCertificateV1,        -- Obsolete
  v2AttrCert [2] IMPLICIT AttributeCertificateV2,
  other [3] IMPLICIT OtherCertificateFormat }

AttributeCertificateV2 ::= AttributeCertificate

OtherCertificateFormat ::= SEQUENCE {
  otherCertFormat OBJECT IDENTIFIER,
  otherCert ANY DEFINED BY otherCertFormat }

CertificateSet ::= SET OF CertificateChoices

IssuerAndSerialNumber ::= SEQUENCE {
  issuer Name,
  serialNumber CertificateSerialNumber }

CMSVersion ::= INTEGER
--## CMSVersion ::= INTEGER  { v0(0), v1(1), v2(2), v3(3), v4(4), v5(5) }

UserKeyingMaterial ::= OCTET STRING

OtherKeyAttribute ::= SEQUENCE {
  keyAttrId OBJECT IDENTIFIER,
  keyAttr ANY DEFINED BY keyAttrId OPTIONAL }

-- Content Type Object Identifiers

--## id-ct-contentInfo OBJECT IDENTIFIER ::= { iso(1) member-body(2)
--##     us(840) rsadsi(113549) pkcs(1) pkcs9(9) smime(16) ct(1) 6 }

--## id-data OBJECT IDENTIFIER ::= { iso(1) member-body(2)
--##     us(840) rsadsi(113549) pkcs(1) pkcs7(7) 1 }

--## id-signedData OBJECT IDENTIFIER ::= { iso(1) member-body(2)
--##     us(840) rsadsi(113549) pkcs(1) pkcs7(7) 2 }

--## id-envelopedData OBJECT IDENTIFIER ::= { iso(1) member-body(2)
--##     us(840) rsadsi(113549) pkcs(1) pkcs7(7) 3 }

--## id-digestedData OBJECT IDENTIFIER ::= { iso(1) member-body(2)
--##     us(840) rsadsi(113549) pkcs(1) pkcs7(7) 5 }

--## id-encryptedData OBJECT IDENTIFIER ::= { iso(1) member-body(2)
--##     us(840) rsadsi(113549) pkcs(1) pkcs7(7) 6 }
--## id-ct-authData OBJECT IDENTIFIER ::= { iso(1) member-body(2)
--##     us(840) rsadsi(113549) pkcs(1) pkcs-9(9) smime(16) ct(1) 2 }

-- The CMS Attributes

MessageDigest ::= OCTET STRING

SigningTime  ::= Time

Time ::= CHOICE {
  utcTime UTCTime,
  generalTime GeneralizedTime }

Countersignature ::= SignerInfo

-- Attribute Object Identifiers

--## id-contentType OBJECT IDENTIFIER ::= { iso(1) member-body(2)
--##     us(840) rsadsi(113549) pkcs(1) pkcs9(9) 3 }

--## id-messageDigest OBJECT IDENTIFIER ::= { iso(1) member-body(2)
--##     us(840) rsadsi(113549) pkcs(1) pkcs9(9) 4 }

--## id-signingTime OBJECT IDENTIFIER ::= { iso(1) member-body(2)
--##     us(840) rsadsi(113549) pkcs(1) pkcs9(9) 5 }

--## id-countersignature OBJECT IDENTIFIER ::= { iso(1) member-body(2)
--##     us(840) rsadsi(113549) pkcs(1) pkcs9(9) 6 }

-- Obsolete Extended Certificate syntax from PKCS #6

ExtendedCertificateOrCertificate ::= CHOICE {
  certificate Certificate,
  extendedCertificate [0] IMPLICIT ExtendedCertificate }

ExtendedCertificate ::= SEQUENCE {
  extendedCertificateInfo ExtendedCertificateInfo,
  signatureAlgorithm SignatureAlgorithmIdentifier,
  signature Signature }

ExtendedCertificateInfo ::= SEQUENCE {
  version CMSVersion,
  certificate Certificate,
  attributes UnauthAttributes }

Signature ::= BIT STRING

--## END -- of CryptographicMessageSyntax2004
